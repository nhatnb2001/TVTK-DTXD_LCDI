(defun c:ss() ; 
(setvar "cmdecho" 0)
(setvar "DIMZIN" 0)
(if (= Ty_le nil)
(progn
(setq Ty_le (getreal "\Nnhap ti le <1000>:"))
(if (= Ty_le nil)(setq Ty_le 1000.00))
)
(progn
(setq khaibaoTy_le (getstring (strcat "\nti le = " (rtos Ty_le 2 0) " CO MUON THAY DOI KHONG <K>,C:")))
(if (= (strlen khaibaoTy_le) 0) (setq khaibaoTy_le "K"))
(if (or (= khaibaoTy_le "k") (= khaibaoTy_le "K"))
(progn
(princ (strcat "\nti le = " (rtos Ty_le 2 0)))
)
(if (or (= khaibaoTy_le "c") (= khaibaoTy_le "C"))
(progn
(setq Ty_le (getreal "\nnhap ti le <1000>:"))
(if (= Ty_le nil)(setq Ty_le 1000.00))
)
) 
)
)
)
(if (= So_Le nil)
(progn
(setq So_Le (getint "\nnhap so le dien tich <2>:"))
(if (= So_Le nil)(setq So_Le 2))
)
(progn
(setq khaibaoSo_Le (getstring (strcat "\nso le dien tich = " (rtos So_Le 2 0) " co muon thay doi khong <K>,C:")))
(if (= (strlen khaibaoSo_Le) 0) (setq khaibaoSo_Le "K"))
(if (or (= khaibaoSo_Le "k") (= khaibaoSo_Le "K"))
(progn
(princ (strcat "\nso le dien tich = " (rtos So_Le 2 0)))
)
(if (or (= khaibaoSo_Le "c") (= khaibaoSo_Le "C"))
(progn
(setq So_Le (getint "\nnhap so le dien tich <2>:"))
(if (= So_Le nil)(setq So_Le 2))
)
) 
)
)
)
(setq He_so (/ 1000 Ty_le))
(setq He_so2 (* He_so He_so)) 
(setq dtl 0)
(setq ss (ssadd))
(setq oslast (getvar "OSMODE"))
(command "osnap" "")
(print)
(print)
(setq pt1 (getpoint "\nChon Vung Kin Tinh Dien Tich : "))
(while (/= pt1 nil)
(command "-boundary" pt1 "")
(setq et (entlast))
(ssadd et ss)
(command "area" "e" "last")
(setq vsize ( /(getvar "VIEWSIZE") 50 ))
(command "hatch" "ANSI31" vsize "0" "last" "")
(setq et (entlast))
(ssadd et ss)
(setq dtcon (getvar "AREA"))
(setq dtl (+ dtcon dtl))
(print)
(print)
(setq pt1 (getpoint "\nChon Vung Kin Tinh Dien Tich : "))
)
(command "setvar" "OSMODE" oslast)
(command "erase" ss "")
(setq ss nil)
(command "redraw")
(setq dtl (/ (/ dtl He_so2) 1)) 
(setq en (car (entsel "Thay cho so : ")))
(while (= en nil)
(setq en (car (entsel "Thay cho so : ")))
)
(setq elst (entget en))
(setq elstold (assoc 1 elst)) 
(setq elstnew (cons 1 (rtos dtl 2 So_Le)))
(setq elst (subst elstnew elstold elst))
(entmod elst)
(setq elst nil)
(setq dtl nil)
(command "_change" en "" "p" "c" "1" "")
(princ "\nhttp:\\doanduyhung.googlepages.com")
)
