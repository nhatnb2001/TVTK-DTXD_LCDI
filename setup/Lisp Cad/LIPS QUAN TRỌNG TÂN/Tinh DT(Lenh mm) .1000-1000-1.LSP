(defun c:MM()
  (if (= Ty_le_N nil) (progn
    (setq Ty_le_N (getreal "\nnHorizontal Drawing scale : "))
    (setq He_so (/ 1000 Ty_le_N))
    (setq Ty_le_D (getreal "\nVertical Drawing scale : "))
    (setq He_so1 (/ 1000 Ty_le_D))
    (setq He_so2 (* He_so He_so1))
    )
  )
  (if (= vol nil) (progn
    (setq vol (getreal "\nAll Quanttities or Half: "))
    )
  )
  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (setq vsize ( /(getvar "VIEWSIZE") 150 ))
    (command "hatch" "ANSI31" vsize "0" "last" "")
    (setq et (entlast))
    (ssadd et ss)
    (setq dtcon (getvar "AREA"))
    (setq dtl (+ dtcon dtl))
    (print)
    (print)
    (setq pt1 (getpoint "\nPick internal point : "))
  )
    (command "setvar" "OSMODE" oslast)
  (command "erase" ss "")
  (setq ss nil)
  (command "redraw")
  (command "zoom" "w" pgoc1 pgoc2)
  (setq dtl (- (/ (/ dtl He_so2) vol) 0))
(REPEAT 1
  (setq en (car (entsel "Thay cho so : ")))
  (setq elst (entget en))
  (setq elst (subst (cons 1 (strcat " " (rtos dtl 2 2))) (assoc 1 elst) elst))
  (setq elst (append elst '((62 . 4))))
  (prin1 elst)
  (entmod elst)
) 
  (print)
  (prompt (strcat "\nTotal area : " (rtos dTy_le 2 4)))
  (print)
  (setq pt2 (getpoint "\nPoint to write: "))
 (command "text" pt2 (/ vsize 6) "0" (rtos dtl 7 3))
);defun
